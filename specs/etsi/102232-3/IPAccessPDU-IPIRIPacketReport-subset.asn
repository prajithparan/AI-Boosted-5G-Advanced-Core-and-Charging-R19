IPAccessPDU
{itu-t(0) identified-organization(4) etsi(0) securityDomain(2) lawfulIntercept(2) li-ps(5) iPAccess(3) version18(18)}

DEFINITIONS IMPLICIT TAGS ::=
BEGIN

-- Subset generated by tools/li-asn1/trim_ipaccess.py: the closure of
-- IPIRIPacketReport, verbatim from the ETSI source. See that script for why.

IPIRIPacketReport ::= SEQUENCE
{
    iPIRIPacketReportObjId [0] RELATIVE-OID,
    report                 [1] PacketReport,
    ...
}

PacketReport ::= CHOICE
{
    header  [1] PacketReportHeader,
    summary [2] PacketReportSummary,
    ...
}

PacketReportHeader ::= SEQUENCE
{
    header [1] OCTET STRING,
    ...
}

PacketReportSummary ::= SEQUENCE
{
    header         [1] OCTET STRING,
    indications    [2] PacketReportIndications,
    trigger        [3] PacketReportTrigger,
    packetCount    [4] INTEGER OPTIONAL,
    byteCount      [5] INTEGER OPTIONAL,
    firstTimestamp [6] GeneralizedTime OPTIONAL,
    lastTimestamp  [7] GeneralizedTime OPTIONAL,
    ...
}

PacketReportIndications ::= BIT STRING
{
    zeroedIPv4TotalLength(0),
    zeroedIPv4Flags(1),
    zeroedIPv4TimeToLive(2),
    zeroedIPv4HeaderChecksum(3),
    zeroedIPv6PayloadLength(4),
    removedIPv6ExtensionHeaders(5),
    zeroedTCPSequenceNumber(6),
    zeroedTCPAcknowledgementNumber(7),
    zeroedTCPFlags(8),
    zeroedTCPWindowSize(9),
    zeroedTCPChecksum(10),
    zeroedUDPLength(11),
    zeroedUDPChecksum(12)
}

PacketReportTrigger ::= ENUMERATED
{
    flowStart(1),
    flowEnd(2),
    flowTimeout(3),
    flowTimerExpiration(4),
    flowPacketCount(5),
    flowByteCount(6),
    sessionTimerExpiration(7),
    sessionPacketCount(8),
    sessionByteCount(9),
    reportEnd(10),
    ...
}

END
